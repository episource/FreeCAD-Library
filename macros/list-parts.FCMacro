# -*- coding: utf-8 -*-

__Name__ = 'list-parts'
__Comment__ = 'Formats all parts referenced in an assembly as spreadsheet'
__Author__ = 'Philipp Serr (episource.de)'
__Version__ = '0.4'
__Date__ = '2020-06-04'
__License__ = 'CC-BY-4.0'
__Web__ = 'https://github.com/episource/freecad-library'
__Wiki__ = ''
__Icon__ = ''
__Help__ = 'Just run this macro. A spreadsheet "parts" will be (re)created.'
__Status__ = 'Beta'
__Requires__ = 'FreeCAD >= 0.19'
__Communication__ = ''


fastenersFound = False

import collections
import itertools
import re
import FreeCAD as App
from FreeCAD import Units
try:
    import FastenersCmd
    fastenersFound = True
except ImportError:
    pass


PARTS_ALL_SHEET_NAME = "parts"
PARTS_SUBASSY_SHEET_NAME = "parts_subassemblies"
ROOT_MODEL_NAME = "Model"
DEFAULT_MODEL_TYPE = "Assembly4 Model"
STRING_WITH_NUMERIC_SUFIX = re.compile("(?P<num>^[0-9]+)(?P<str>.*)")


def printError(msg):
    print(__Name__ + ": " + msg, file=sys.stderr)

def tryGet(obj, attr, default=''):
    result = None
    if hasattr(obj, attr):
        result = str(getattr(obj, attr))
    elif hasattr(obj, attr.lower()):
        result = str(getattr(obj, attr.lower()))
    
    if not result:
        result = default
    return result

def isAssembly4Model(partObject):
    return partObject is not None \
        and hasattr(partObject, "TypeId") and partObject.TypeId == "App::Part" \
        and hasattr(partObject, "Name") and partObject.Name == "Model"

def expandNumericSufix(string):
    m = STRING_WITH_NUMERIC_SUFIX.match(string)
    if m is None:
        return string
    groups = m.groupdict()
    groups['num'] = int(groups['num'])
    return "{num:015d}{str}".format(**groups)

def getId(partDesc):
    return getIdWithoutDoc(partDesc) + "_" + partDesc['doc']
    
def getIdWithoutDoc(partDesc):
    return expandNumericSufix(partDesc['partType']) + "_" + expandNumericSufix(partDesc['userLabel'])

def getTypeOfAssy(assy):
    if assy.Type == DEFAULT_MODEL_TYPE:
        if assy.Label == ROOT_MODEL_NAME:
            return assy.Document.Label
        return assy.Label
    return assy.Type

def addPart(parts, part, fullAssyName):
    if 'Assembly4 Model' in part.Type and part.Document == App.ActiveDocument:
        # suppress root model
        return
    partDesc = {
        "doc": part.Document.Label,
        "assy": fullAssyName,
        "uniqueLabel": tryGet(part, 'Label'),
        "partType": tryGet(part, 'Type', default=part.Label),
        "userLabel": tryGet(part, 'Label2'),
        "desc": tryGet(part, 'Desc', tryGet(part, 'Description'))
    }
    
    if isAssembly4Model(part):
        partDesc['partType'] = getTypeOfAssy(part)
    
    parts.append(partDesc)

def addFeatureIfPartLike(parts, feature, fullAssyName):
    partDesc = {
        "doc": feature.Document.Label,
        "assy": fullAssyName,
        "uniqueLabel": tryGet(feature, 'Label'),
        "partType": tryGet(feature, 'Type', feature.Label),
        "userLabel": tryGet(feature, 'Label2'),
        "desc": tryGet(feature, 'Desc', tryGet(feature, 'Description'))
    }
    if fastenersFound:
        if hasattr(feature, 'Proxy') and issubclass(type(feature.Proxy), FastenersCmd.FSScrewObject):
            partDesc["partType"] = "Screw/Bolt " + feature.type
            sufix = "" if not partDesc["userLabel"] else " | " + partDesc["userLabel"]
            length = feature.length if not feature.length == "Custom" else "{:g}".format(feature.lengthCustom.Value)
            partDesc["userLabel"] = feature.diameter + "x" + length + sufix
            parts.append(partDesc)

def scanForParts(objects, qualifiedAssy, expandSubAssy=True, parts=[]):
    if not isinstance(qualifiedAssy, str):
        qualifiedAssy = getTypeOfAssy(qualifiedAssy)

    for obj in objects:
        if hasattr(obj, 'TypeId'):
            if "App::Part" in obj.TypeId:
                if isAssembly4Model(obj):
                    subAssy = qualifiedAssy + "/" + getTypeOfAssy(obj)
                    
                    isAtomic = tryGet(obj, "IsAtomicPart", False)
                    isTransient = tryGet(obj, "IsTransientPart", False)
                        
                    if (expandSubAssy or isTransient) and not isAtomic:
                        scanForParts(obj.Group, subAssy, expandSubAssy=expandSubAssy, parts=parts)
                    else:
                        addPart(parts, obj, subAssy)
                else:
                    addPart(parts, obj, qualifiedAssy)
            elif "Part::Feature" in obj.TypeId:
                addFeatureIfPartLike(parts, obj, qualifiedAssy)
            elif "App::Link" in obj.TypeId:
                scanForParts([obj.LinkedObject], qualifiedAssy, expandSubAssy=expandSubAssy, parts=parts)
                
    return parts

def getOrCreateResultSheet(sheetName):
    sheet = App.ActiveDocument.getObject(sheetName)
    if sheet is None:
        sheet = App.ActiveDocument.addObject("Spreadsheet::Sheet", sheetName)
    elif 'Spreadsheet::Sheet' not in sheet.TypeId:
        printError("an object named '" + sheetName + "' exists, but is not of type spreadsheet")
        sheet = None
    return sheet

def setCell(sheet, col, row, value, style=None):
    if value is None:
        text = ''
    elif isinstance(value, Units.Quantity):
        text = value.UserString
    else:
        text = str(value)
    
    ref = col + str(row)
    sheet.set(ref, "'" + text)

    if style is not None:
        sheet.setStyle(ref, style, 'add')

def writeResults(sheet, parts):
    preservedWidth = sheet.columnWidths.dumpContent()
    sheet.clearAll()
    sheet.columnWidths.restoreContent(preservedWidth)
    
    setCell(sheet, 'A', 1, 'Part List: ' + App.ActiveDocument.Label, 'bold|underline')
    sheet.mergeCells('A1:D1')
    setCell(sheet, 'A', 2, 'Quantity', 'bold')
    setCell(sheet, 'B', 2, 'Type', 'bold')
    setCell(sheet, 'C', 2, 'Label', 'bold')
    setCell(sheet, 'D', 2, 'Assembly', 'bold')
    setCell(sheet, 'E', 2, 'Document', 'bold')
    setCell(sheet, 'F', 2, 'Description', 'bold')
    
    row = 2
    for k,g in itertools.groupby(sorted(parts, key=getId), key=getIdWithoutDoc):
        row += 1
        gList = list(g)
        quantity = len(gList)
        desc = gList[0]
        
        uniqueDocs = list(collections.Counter(x['doc'] for x in gList).keys())
        docs = ",\n".join(uniqueDocs)
        uniqueAssemblies = list(collections.Counter(x['assy'] for x in gList).keys())
        assemblies = ",\n".join(uniqueAssemblies)
        
        setCell(sheet, 'A', row, quantity)
        setCell(sheet, 'B', row, desc['partType'])
        setCell(sheet, 'C', row, desc['userLabel'])
        setCell(sheet, 'D', row, assemblies)
        setCell(sheet, 'E', row, docs)
        setCell(sheet, 'F', row, desc['desc'])
        
        heightFactor = max(len(uniqueDocs), len(uniqueAssemblies))
        initialRowHeight = sheet.getRowHeight(str(row))
        sheet.setRowHeight(str(row), heightFactor * initialRowHeight)
    
    sheet.recompute()

if App.ActiveDocument is not None:
    d = App.ActiveDocument
    sheetAllParts = getOrCreateResultSheet(PARTS_ALL_SHEET_NAME)
    sheetSubAssyParts = getOrCreateResultSheet(PARTS_SUBASSY_SHEET_NAME)

    if not isAssembly4Model(d.getObject(ROOT_MODEL_NAME)):
        printError("assembly4 model missing in active document: no object named '" + ROOT_MODEL_NAME + "' found or invalid type")
    elif sheetAllParts is None or sheetSubAssyParts is None:
        printError("failed to initialize result spreadsheets")
    else:
        model = d.getObject(ROOT_MODEL_NAME)
        
        parts = scanForParts(model.Group, model, expandSubAssy=True, parts=[])
        writeResults(sheetAllParts, parts)
        
        parts = scanForParts(model.Group, model, expandSubAssy=False, parts=[])
        writeResults(sheetSubAssyParts, parts)
else:
    printError("no active document")
